FME workspace numbeo_fme_scraper.fmw

Creator
    GEOMTYPE = Geometry Object
    NUM = 1
    CREATED -> PythonCaller_Scraper
Note: Change/add country on line 101
PythonCaller_Scraper
    NEW_ATTRIBUTES = json_output input_country
    PYTHONSOURCE:
      """
      Created on Tue Dec 12 11:07:19 2017

      @author: mounic

      Edited on Sat 11.01.2020
      @edited by: Mateusz Pitura
      """
      from fmeobjects import FMEFeature, FME_ATTR_REAL32
      import requests
      from bs4 import BeautifulSoup
      import json

      class FeatureProcessor(object):

          def __init__(self):
              pass

          def input(self, feature):
              pass

          def close(self):
                      # -*- coding: utf-8 -*-

              URL = "https://www.numbeo.com/cost-of-living/"

              class Extract_table:
                  """ Extracts the table from the beautiful soup html page"""
                  def __init__(self, page):
                      self.Data = {}
                      self.Table = page.find("table", {'class':'data_wide_table'}) #finding table with class name
                  def extract(self):
                      """A method to extract the table contents and store to a dict"""
                      if not self.Table:
                          return None #check if it is in the formate.
                      for row in self.Table("tr"):
                          if row("th"):
                              key = row("th")[0].text
                              self.Data[key] = []
                          else:
                              self.Data[key].append([cell.text for cell in row("td")])
                      return self.Data

              class API(object):
                  """API to get a country"""
                  def __init__(self, BASE_URL, Country, city=0):
                      self.base = BASE_URL
                      self.url = BASE_URL+"country_result.jsp?country="+Country
                      self.country = Country
                      self.result = {}
                      responce = self.get_page(self.url)
                      if responce:
                          self.page = BeautifulSoup(responce.text, "html")
                          self.get_city()
                          EX = Extract_table(self.page)
                          self.result[Country] = EX.extract()
                          if city:
                              self.get_all_city()
                      else:
                          self.page = None
                          self.city = None
                  def get_result(self):
                      """returns the result for the country"""
                      return self.result[self.country]

                  def get_page(self, url):
                      """ get the page from the url"""
                      request = requests.get(url)
                      if request.status_code != 200:
                          return None
                      return request

                  def get_city(self):
                      """get all the city"""
                      self.city_form = self.page.find("form", {"class": "standard_margin"})
                      self.city = [values["value"] for values in self.city_form("option")]

                  def get_single_city(self, city):
                      """ get table with the city name for the country"""
                      country = self.country
                      city_page = self.base+"/city_result.jsp?country="+country+"&city="+city
                      self.city_page = BeautifulSoup(self.get_page(city_page).text, "html")
                      table = Extract_table(self.city_page)
                      return table.extract()

                  def get_all_city(self):
                      """ get the table of all the city and returns as a dict"""
                      country = self.country
                      self.result[country]["child"] = {}
                      for city in self.city:
                          print('crawling Country -> %s, city -> %s'%(country, city))
                          self.result[country]["child"][city] = self.get_single_city(city)

              def write_json(FILE, OBJECT):
                  """ Function to store as a json file"""
                  with open(FILE, 'w') as w:
                      w.write(json.dumps(OBJECT))
                  print("The file has written ...")

              if __name__ == "__main__":
                  COUNTRY = ['Poland']
                  print(COUNTRY)
                  results = {}
                  city = 1 #set 1 to crawl all city
                  for i in COUNTRY:
                      obj = API(URL, i, city)
                      results[i] = obj.get_result()
                  write_json("results.json",results) #uncomment to save the results.
                  #print(results)
              feature = FMEFeature()
              json_output = ''
              feature.setAttribute('json_output', json.dumps(results))
              self.pyoutput(feature)
    PYTHONSYMBOL = FeatureProcessor
    -> JSONFormatter
JSONFormatter
    ERROR_LIST_ATTR = _json_error
    FORMAT = Pretty Print
    INDENT_STYLE = 3 spaces
    JSON_DOCUMENT = @Value(json_output)
    OUTPUT_ATTR = json_output_formatted
    OUTPUT_ENCODING = UTF-8
    READ_FROM_FILE = NO
    REMOVE_EMPTY_OBJECTS_AND_ARRAYS = No
    REMOVE_EMPTY_STRINGS = No
    REMOVE_NULLS = No
    -> JSONFragmenter
JSONFragmenter
    EXPLODE_FORMAT = JSON
    EXTRACT_ATTR = No
    JSON_ATTR = json_output_formatted
    JSON_QUERY = json[*]
    READ_FROM_FILE = NO
    REJECT_EMPTY_LISTS = NO
    FRAGMENTS -> AttributeRenamer_Country
AttributeRenamer_Country
    ATTR_TABLE = RENAME_SET_DEFAULT json_index > country
    -> JSONFragmenter_2
JSONFragmenter_2
    EXPLODE_FORMAT = JSON
    EXTRACT_ATTR = No
    JSON_ATTR = json_output_formatted
    JSON_QUERY = json[*]
    READ_FROM_FILE = NO
    REJECT_EMPTY_LISTS = NO
    FRAGMENTS -> AttributeRenamer_Category
AttributeRenamer_Category
    ATTR_TABLE = RENAME_SET_DEFAULT json_index > category
    -> JSONFragmenter_3
JSONFragmenter_3
    EXPLODE_FORMAT = JSON
    EXTRACT_ATTR = No
    JSON_ATTR = json_output_formatted
    JSON_QUERY = json[*]
    READ_FROM_FILE = NO
    REJECT_EMPTY_LISTS = NO
    FRAGMENTS -> AttributeRenamer_CatIndex
AttributeRenamer_CatIndex
    ATTR_TABLE = RENAME_SET_DEFAULT json_index > category_index
    -> TestFilter
TestFilter
    DEFAULT_VALUE = Drop
    TEST_LIST:
      "BOOL_OP,OR,COMPOSITE_TEST,""""""1"""""",TEST_CLAUSE,TEST @Value(category) != child",WholeCountry,"BOOL_OP,AND,COMPOSITE_TEST,""""""1 AND 2"""""",TEST_CLAUSE,TEST @Value(category) = child
      TEST @Value(json_output_formatted) != null",City
    WholeCountry -> JSONFragmenter_4
    City -> JSONFragmenter_5
JSONFragmenter_5
    EXPLODE_FORMAT = JSON
    EXTRACT_ATTR = No
    JSON_ATTR = json_output_formatted
    JSON_QUERY = json[*]
    READ_FROM_FILE = NO
    REJECT_EMPTY_LISTS = NO
    FRAGMENTS -> AttributeRenamer_5
AttributeRenamer_5
    ATTR_TABLE:
      RENAME_SET_DEFAULT json_index > category
      RENAME_SET_DEFAULT category_index > city
    -> JSONFragmenter_6
JSONFragmenter_6
    EXPLODE_FORMAT = JSON
    EXTRACT_ATTR = No
    JSON_ATTR = json_output_formatted
    JSON_QUERY = json[*]
    READ_FROM_FILE = NO
    REJECT_EMPTY_LISTS = NO
    FRAGMENTS -> AttributeRenamer_6
AttributeRenamer_6
    ATTR_TABLE = RENAME_SET_DEFAULT json_index > category_index
    -> JSONFragmenter_7
JSONFragmenter_7
    EXPLODE_FORMAT = JSON
    EXTRACT_ATTR = No
    JSON_ATTR = json_output_formatted
    JSON_QUERY = json[*]
    READ_FROM_FILE = NO
    REJECT_EMPTY_LISTS = NO
    FRAGMENTS -> AttributeRenamer_7
AttributeRenamer_7
    ATTR_TABLE = RENAME_SET_DEFAULT json_index > item_index
    -> Tester_RemoveUnnecesseryValues_2
Tester_RemoveUnnecesseryValues_2
    BOOL_OP = OR
    COMPOSITE_TEST = 1
    TEST_CLAUSE = TEST @Value(item_index) != 2
    TEST_MODE = TEST
    PASSED -> AttributeManager_4
AttributeManager_4
    ATTR_TABLE = SET_TO price = FME_CONDITIONAL:DEFAULT_VALUE'_FME_NO_OP_'BOOL_OP;OR;COMPOSITE_TEST;1;TEST @Value(item_index) = 1'@Trim(@Value(json_output_formatted))'FME_NUM_CONDITIONS2___
    -> Aggregator_2
Aggregator_2
    ACCUM_ATTRS_NAME = Merge Incoming Attributes
    GROUP_BY = category category_index city country
    MODE = Attributes Only
    SEP = ,
    AGGREGATE -> AttributeSplitter
AttributeSplitter
    ATTR_NAME = price
    DELIMITER = " "
    DROP_EMPTY_PARTS = No
    LIST_NAME = _price
    TRIM_OPTION = None
    -> ListExploder
ListExploder
    ATTR_ACCUM_MODE = Merge List Attributes
    ATTR_CONFLICT_RES = Use List Attribute Values
    INDEX_ATTR = _price_element_index
    LIST_ATTR = _price{}
    ELEMENTS -> AttributeManager_ValueAndCurrencySetter
AttributeManager_ValueAndCurrencySetter
    ATTR_TABLE:
      SET_TO currency = FME_CONDITIONAL:DEFAULT_VALUE'_FME_NO_OP_'BOOL_OP;OR;COMPOSITE_TEST;1;TEST @Value(_price_element_index) = 1'@Value(_price)'FME_NUM_CONDITIONS2___
      SET_TO value = FME_CONDITIONAL:DEFAULT_VALUE'_FME_NO_OP_'BOOL_OP;OR;COMPOSITE_TEST;1;TEST @Value(_price_element_index) = 0'@Value(_price)'FME_NUM_CONDITIONS2___
    -> Aggregator_3
Aggregator_3
    ACCUM_ATTRS_NAME = Merge Incoming Attributes
    GROUP_BY = category category_index city item_index json_type country fme_feature_type price
    MODE = Attributes Only
    SEP = ,
    AGGREGATE -> Sorter
Sorter
    SORT_PARM = country ALPHA ASCENDING city ALPHA ASCENDING category ALPHA ASCENDING category_index NUMERIC ASCENDING
    SORTED -> AttributeManager_3
AttributeManager_3
    ATTR_TABLE:
      RENAME_SET_VALUE json_output_formatted > item
      REMOVE item_index
      REMOVE json_type
      REMOVE json_output
      REMOVE _price
      REMOVE _price_element_index
    -> Geocoder_2
Note: Use OSM or your API
Geocoder_2
    GEOCODING_SERVICE = OpenStreetMap
    THREADS = 4
    TIMEOUT = 60
    -> StringReplacer
StringReplacer
    CASE = NO
    FIND_TEXT = ,
    NO_MATCH = _FME_NO_OP_
    REGEXP = NO
    SRC_ATTRS = value,price
    -> AttributeManager_5
AttributeManager_5
    ATTR_TABLE:
      SET_TO category_index = @Evaluate(@int(@Value(category_index)))
      SET_TO value = @Evaluate(@real32(@round(@Value(value),2)))
    -> AttributeValueMapper
AttributeValueMapper
    DEFAULT_VALUE = @Value(city)
    DIRECTION = Forward (Source To Destination)
    LUT = Warsaw,Warszawa,Gdansk,Gdańsk,Lodz,Łódź,Ostrow Wielkopolski (Ostrów Wielkopolski),Ostrów Wielkopolski,Krakow (Cracow),Kraków,Torun,Toruń,Poznan,Poznań,Wroclaw,Wrocław,Elblag,Elbląg,Pila,Piła,Gorzow Wielkopolski,Gorzów Wielkopolski,Bialystok,Białystok,Zielona Gora,Zielona Góra,Jelenia Gora,Jelenia Góra,Walbrzych,Wałbrzych,Czestochowa,Częstochowa,Chorzow,Chorzów,Bielsko-biala,Bielsko-Biała,Nowy Sacz,Nowy Sącz,Tarnow,Tarnów,Rzeszow,Rzeszów
    SRC = city
    VAL_ATTR = city
    -> FeatureWriter_Cities [Output]
FeatureWriter_Cities
    DATASET = C:\GoogleDrive - mateuszpitura\smartcarto.com\datasets\poland_data_numbeo\poland_cities.json
    DATASET_ATTR = _dataset
    FEATURE_TYPE_LIST_ATTR = _feature_type
    FORMAT = GEOJSON
    GEOJSON_COUNTER_CLOCKWISE_AREAS = Yes
    GEOJSON_DESTINATION_DATASETTYPE_VALIDATION = Yes
    GEOJSON_INDENT_SIZE = 0
    GEOJSON_MAX_COORDINATE_PRECISION = 10
    GEOJSON_PRETTY_PRINT = YES
    GEOJSON_STRICT_SPEC = Yes
    GEOJSON_WGS84_REPROJECTION = Yes
    GEOJSON_WRITER_CHARSET = UTF-8
    GEOJSON_WRITE_BOM = No
    TOTAL_FEATURES_WRITTEN_ATTR = _total_features_written
JSONFragmenter_4
    EXPLODE_FORMAT = JSON
    EXTRACT_ATTR = No
    JSON_ATTR = json_output_formatted
    JSON_QUERY = json[*]
    READ_FROM_FILE = NO
    REJECT_EMPTY_LISTS = NO
    FRAGMENTS -> AttributeRenamer_ItIndex
AttributeRenamer_ItIndex
    ATTR_TABLE = RENAME_SET_DEFAULT json_index > item_index
    -> Tester_RemoveUnnecesseryValues
Tester_RemoveUnnecesseryValues
    BOOL_OP = OR
    COMPOSITE_TEST = 1
    TEST_CLAUSE = TEST @Value(item_index) != 2
    TEST_MODE = TEST
    PASSED -> AttributeManager_2
AttributeManager_2
    ATTR_TABLE = SET_TO price = FME_CONDITIONAL:DEFAULT_VALUE'_FME_NO_OP_'BOOL_OP;OR;COMPOSITE_TEST;1;TEST @Value(item_index) = 1'@Value(json_output_formatted)'FME_NUM_CONDITIONS2___
    -> Aggregator
Aggregator
    ACCUM_ATTRS_NAME = Merge Incoming Attributes
    GROUP_BY = category category_index country
    MODE = Attributes Only
    SEP = ,
    AGGREGATE -> AttributeSplitter_2
AttributeSplitter_2
    ATTR_NAME = price
    DELIMITER = " "
    DROP_EMPTY_PARTS = No
    LIST_NAME = _price
    TRIM_OPTION = None
    -> ListExploder_2
ListExploder_2
    ATTR_ACCUM_MODE = Merge List Attributes
    ATTR_CONFLICT_RES = Use List Attribute Values
    INDEX_ATTR = _price_element_index
    LIST_ATTR = _price{}
    ELEMENTS -> AttributeManager_ValueAndCurrencySetter_2
AttributeManager_ValueAndCurrencySetter_2
    ATTR_TABLE:
      SET_TO currency = FME_CONDITIONAL:DEFAULT_VALUE'_FME_NO_OP_'BOOL_OP;OR;COMPOSITE_TEST;1;TEST @Value(_price_element_index) = 1'@Value(_price)'FME_NUM_CONDITIONS2___
      SET_TO value = FME_CONDITIONAL:DEFAULT_VALUE'_FME_NO_OP_'BOOL_OP;OR;COMPOSITE_TEST;1;TEST @Value(_price_element_index) = 0'@Value(_price)'FME_NUM_CONDITIONS2___
    -> Aggregator_4
Aggregator_4
    ACCUM_ATTRS_NAME = Merge Incoming Attributes
    GROUP_BY = category category_index item_index json_type country fme_feature_type price
    MODE = Attributes Only
    SEP = ,
    AGGREGATE -> Sorter_2
Sorter_2
    SORT_PARM = country ALPHA ASCENDING category ALPHA ASCENDING category_index NUMERIC ASCENDING
    SORTED -> AttributeManager
AttributeManager
    ATTR_TABLE:
      RENAME_SET_VALUE json_output_formatted > item
      REMOVE item_index
      REMOVE json_type
      REMOVE json_output
      REMOVE _price
      REMOVE _price_element_index
    -> Geocoder
Note: Use OSM or your API
Geocoder
    GEOCODING_SERVICE = OpenStreetMap
    THREADS = 4
    TIMEOUT = 60
    -> FeatureWriter [Output]
FeatureWriter
    DATASET = C:\GoogleDrive - mateuszpitura\smartcarto.com\datasets\poland_data_numbeo\poland.json
    DATASET_ATTR = _dataset
    FEATURE_TYPE_LIST_ATTR = _feature_type
    FORMAT = GEOJSON
    GEOJSON_COUNTER_CLOCKWISE_AREAS = Yes
    GEOJSON_DESTINATION_DATASETTYPE_VALIDATION = Yes
    GEOJSON_INDENT_SIZE = 0
    GEOJSON_MAX_COORDINATE_PRECISION = 10
    GEOJSON_PRETTY_PRINT = YES
    GEOJSON_STRICT_SPEC = Yes
    GEOJSON_WGS84_REPROJECTION = Yes
    GEOJSON_WRITER_CHARSET = UTF-8
    GEOJSON_WRITE_BOM = No
    TOTAL_FEATURES_WRITTEN_ATTR = _total_features_written
PythonCaller_2
    NEW_ATTRIBUTES = raccoons
    PYTHONSOURCE:
      import fme
      from fmeobjects import FMEFeature, FME_ATTR_REAL32
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              self.pyoutput(feature)
          def close(self):
              feature = FMEFeature()
              feature.setAttribute('raccoons', 64)
              self.pyoutput(feature)
    PYTHONSYMBOL = FeatureProcessor
AttributeCreator
    ATTR_TABLE:
      SET_TO json_example = {
           "paramName":"GeocodeResult",
           "dataType":"GPFeatureRecordSetLayer",
           "value":
           {
              "geometryType":"esriGeometryPoint",
              "spatialReference": {"wkid":4326 }
           }
        }
    -> JSONFlattener_2
JSONFlattener_2
    ERROR_LIST_ATTR = _json_error
    JSON_DOCUMENT = @Value(json_example)
    NEW_ATTRIBUTES = paramName json_paramName
    PREFIX_STRING = json_
    READ_FROM_FILE = NO
    RECURSIVE = No
